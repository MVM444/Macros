# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

# ------------------------------------------------------------------------
# RESUMEN:
# Esta clase crea una ventana principal en FreeCAD cargando una interfaz .ui
# diseñada en Qt Designer, usando PySide2 y QUiLoader.
# - Busca el archivo .ui en el directorio de macros de FreeCAD.
# - Si el archivo existe, lo carga y conecta los botones a métodos de la clase.
# - Los métodos muestran mensajes en la consola de FreeCAD al hacer clic.
# - Si el archivo .ui no existe, muestra un error en la consola.
# ------------------------------------------------------------------------import FreeCAD
import FreeCADGui
from PySide2 import QtWidgets, QtCore, QtUiTools
import os

class DiagramaUnifilarApp(QtWidgets.QMainWindow):
    def __init__(self):
        super(DiagramaUnifilarApp, self).__init__()

        # Usar el directorio donde está este archivo
        macro_dir = os.path.dirname(__file__)

        if not os.path.exists(macro_dir):
            FreeCAD.Console.PrintError("El directorio de macros de FreeCAD no existe.\n")
            return

        # Definir la ruta del archivo UI
        ui_file_path = os.path.join(macro_dir, "diagrama_unifilar_ejemplo.ui")

        # Verificar si el archivo UI existe
        if not os.path.exists(ui_file_path):
            FreeCAD.Console.PrintError(f"El archivo UI no se encontró en: {ui_file_path}\n")
            return

        # Cargar el archivo UI
        self.load_ui(ui_file_path)

        # Configurar la ventana
        self.setWindowTitle("Diagrama Unifilar")
        self.resize(800, 600)

        # Conectar los botones o widgets
        self.setup_connections()

    def load_ui(self, ui_file_path):
        """
        Carga la interfaz directamente desde el archivo .ui sin necesidad de conversión.
        """
        try:
            loader = QtUiTools.QUiLoader()
            ui_file = QtCore.QFile(ui_file_path)
            ui_file.open(QtCore.QFile.ReadOnly)

            loaded_ui = loader.load(ui_file, self)
            ui_file.close()

            if loaded_ui:
                self.setCentralWidget(loaded_ui.findChild(QtWidgets.QWidget, "centralwidget"))  # Asigna el centralwidget
                self.ui = loaded_ui

                # Depuración: Imprimir los objetos cargados
                for obj in self.ui.children():
                    FreeCAD.Console.PrintMessage(f"Objeto cargado: {obj.objectName()}\n")

                # Forzar actualización de la ventana
                self.update()
                self.repaint()
            else:
                FreeCAD.Console.PrintError("No se pudo cargar la UI.\n")

        except Exception as e:
            FreeCAD.Console.PrintError(f"Error al cargar la interfaz UI: {str(e)}\n")

    def setup_connections(self):
        """
        Configura las conexiones entre los elementos de la UI y las funciones de la clase.
        """
        try:
            if hasattr(self.ui, "pushButton"):
                self.ui.pushButton.clicked.connect(self.on_pushButton_clicked)

            if hasattr(self.ui, "btnAgregarComponente"):
                self.ui.btnAgregarComponente.clicked.connect(self.on_btnAgregarComponente_clicked)

            if hasattr(self.ui, "btnDibujarConexion"):
                self.ui.btnDibujarConexion.clicked.connect(self.on_btnDibujarConexion_clicked)

        except Exception as e:
            FreeCAD.Console.PrintError(f"Error al configurar conexiones: {str(e)}\n")

    # Métodos para cada botón
    def on_pushButton_clicked(self):
        FreeCAD.Console.PrintMessage("¡Botón 'PushButton' clickeado!\n")

    def on_btnAgregarComponente_clicked(self):
        FreeCAD.Console.PrintMessage("¡Botón 'Agregar Componente' clickeado!\n")

    def on_btnDibujarConexion_clicked(self):
        FreeCAD.Console.PrintMessage("¡Botón 'Dibujar Conexión' clickeado!\n")

# Comprobar si la aplicación se ejecuta dentro de FreeCAD
if FreeCADGui:
    try:
        app = DiagramaUnifilarApp()
        app.show()
    except Exception as e:
        FreeCAD.Console.PrintError(f"Error al inicializar la aplicación: {str(e)}\n")
