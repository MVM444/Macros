# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

import FreeCAD
import FreeCADGui
import re
from PySide2 import QtGui, QtCore, QtWidgets

class RenombrarDialogo(QtWidgets.QDialog):
    def __init__(self, grupo, parent=None):
        super(RenombrarDialogo, self).__init__(parent)
        
        self.grupo = grupo
        self.setWindowTitle("Renombrar Objetos del Grupo")

        # Layout principal
        layout = QtWidgets.QVBoxLayout(self)

        # Campo para el nombre base (label del grupo)
        self.label_grupo = QtWidgets.QLabel(f"Label del Grupo: {grupo.Label}")
        layout.addWidget(self.label_grupo)

        # Campo para el nuevo nombre base
        self.label_base = QtWidgets.QLabel("Nombre base para el objeto:")
        self.input_base = QtWidgets.QLineEdit(self)
        layout.addWidget(self.label_base)
        layout.addWidget(self.input_base)

        # Campo para el separador
        self.label_separador = QtWidgets.QLabel("Separador:")
        self.input_separador = QtWidgets.QLineEdit(self)
        layout.addWidget(self.label_separador)
        layout.addWidget(self.input_separador)

        # Checkbox para incluir el nombre original del objeto
        self.checkbox_nombre_original = QtWidgets.QCheckBox("Incluir nombre original del objeto", self)
        self.checkbox_nombre_original.setChecked(True)
        layout.addWidget(self.checkbox_nombre_original)

        # Lista de objetos
        self.label_lista = QtWidgets.QLabel("Lista de Objetos:")
        layout.addWidget(self.label_lista)
        self.lista_objetos = QtWidgets.QListWidget(self)
        layout.addWidget(self.lista_objetos)

        # Botones para mover objetos en la lista
        self.boton_subir = QtWidgets.QPushButton("Subir", self)
        self.boton_subir.clicked.connect(self.mover_objeto_arriba)
        self.boton_bajar = QtWidgets.QPushButton("Bajar", self)
        self.boton_bajar.clicked.connect(self.mover_objeto_abajo)
        layout.addWidget(self.boton_subir)
        layout.addWidget(self.boton_bajar)

        # Botón para vista preliminar
        self.boton_preliminar = QtWidgets.QPushButton("Vista Preliminar", self)
        self.boton_preliminar.clicked.connect(self.actualizar_preliminar)
        layout.addWidget(self.boton_preliminar)

        # Campo de texto para vista preliminar
        self.preliminar = QtWidgets.QTextEdit(self)
        self.preliminar.setReadOnly(True)
        layout.addWidget(self.preliminar)

        # Botón para aplicar cambios
        self.boton_aplicar = QtWidgets.QPushButton("Aplicar", self)
        self.boton_aplicar.clicked.connect(self.aplicar_cambios)
        layout.addWidget(self.boton_aplicar)

        self.setLayout(layout)
        self.llenar_lista()

    def llenar_lista(self):
        objetos_ordenados = sorted(
            self.grupo.Group,
            key=lambda obj: (extraer_numero(obj.Label), obj.Label)
        )
        for obj in objetos_ordenados:
            self.lista_objetos.addItem(obj.Label)

    def mover_objeto_arriba(self):
        current_row = self.lista_objetos.currentRow()
        if current_row > 0:
            item = self.lista_objetos.takeItem(current_row)
            self.lista_objetos.insertItem(current_row - 1, item)
            self.lista_objetos.setCurrentRow(current_row - 1)

    def mover_objeto_abajo(self):
        current_row = self.lista_objetos.currentRow()
        if current_row < self.lista_objetos.count() - 1:
            item = self.lista_objetos.takeItem(current_row)
            self.lista_objetos.insertItem(current_row + 1, item)
            self.lista_objetos.setCurrentRow(current_row + 1)

    def actualizar_preliminar(self):
        base = self.input_base.text()
        separador = self.input_separador.text()
        incluir_nombre_original = self.checkbox_nombre_original.isChecked()
        vista_preliminar = []

        for i in range(self.lista_objetos.count()):
            obj_label = self.lista_objetos.item(i).text()
            nuevo_label = f"{self.grupo.Label}{separador}{base}"
            if incluir_nombre_original:
                nuevo_label += f"{separador}{obj_label}"
            nuevo_label += f"{separador}{str(i+1).zfill(2)}"
            vista_preliminar.append(f"{obj_label} -> {nuevo_label}")
        
        self.preliminar.setText("\n".join(vista_preliminar))

    def aplicar_cambios(self):
        base = self.input_base.text()
        separador = self.input_separador.text()
        incluir_nombre_original = self.checkbox_nombre_original.isChecked()

        objetos_dict = {obj.Label: obj for obj in self.grupo.Group}

        for i in range(self.lista_objetos.count()):
            obj_label = self.lista_objetos.item(i).text()
            nuevo_label = f"{self.grupo.Label}{separador}{base}"
            if incluir_nombre_original:
                nuevo_label += f"{separador}{obj_label}"
            nuevo_label += f"{separador}{str(i+1).zfill(2)}"
            obj = objetos_dict[obj_label]
            obj.Label = nuevo_label
        
        FreeCAD.ActiveDocument.recompute()
        self.accept()

def extraer_numero(label):
    match = re.search(r'\d+', label)
    return int(match.group()) if match else float('inf')

def renombrar_labels_con_dialogo():
    doc = FreeCAD.ActiveDocument
    selected_objects = FreeCADGui.Selection.getSelection()
    
    if not selected_objects:
        FreeCAD.Console.PrintError("No se ha seleccionado ningún objeto.\n")
        return
    
    if selected_objects[0].TypeId == 'App::DocumentObjectGroup':
        grupo = selected_objects[0]
    else:
        for obj in doc.Objects:
            if obj.TypeId == 'App::DocumentObjectGroup' and selected_objects[0] in obj.Group:
                grupo = obj
                break
        else:
            FreeCAD.Console.PrintError("El objeto seleccionado no pertenece a ningún grupo.\n")
            return

    dialog = RenombrarDialogo(grupo)
    dialog.exec_()

# Ejecuta la función para abrir el cuadro de diálogo de renombrado
renombrar_labels_con_dialogo()
