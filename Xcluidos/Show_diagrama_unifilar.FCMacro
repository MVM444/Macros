# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

import FreeCAD
import FreeCADGui
from PySide2 import QtWidgets, QtCore, QtUiTools
import os

class DiagramaUnifilarApp(QtWidgets.QWidget):
    def __init__(self):
        super(DiagramaUnifilarApp, self).__init__()

        # Ruta al archivo .ui
        ui_file_path = "C:\\Users\\mmfallas\\OneDrive - Caja Costarricense de Seguro Social\\Documentos\\FreeCAD\\Macros\\diagrama_unifilar_ejemplo.ui"

        if not os.path.exists(ui_file_path):
            FreeCAD.Console.PrintError("El archivo UI no se encontró en la ruta especificada.\n")
            return

        # Cargar la UI usando QUiLoader
        try:
            loader = QtUiTools.QUiLoader()
            ui_file = QtCore.QFile(ui_file_path)
            if not ui_file.open(QtCore.QFile.ReadOnly):
                FreeCAD.Console.PrintError("No se pudo abrir el archivo UI.\n")
                return
            
            # Cargar el diseño en el widget actual
            self.ui = loader.load(ui_file, self)
            ui_file.close()

            # Configurar la ventana principal
            self.setWindowTitle("Diagrama Unifilar")
            self.resize(800, 600)

            # Conectar los botones o widgets
            self.setup_connections()
        
        except Exception as e:
            FreeCAD.Console.PrintError(f"Error al cargar la interfaz: {str(e)}\n")
            return

    def setup_connections(self):
        """
        Configura las conexiones entre los elementos de la UI y las funciones de la clase.
        """
        try:
            # Ejemplo: Conexión de un botón (reemplazar 'btnEjemplo' por el objeto de tu UI)
            if hasattr(self.ui, "btnEjemplo"):
                self.ui.btnEjemplo.clicked.connect(self.on_btnEjemplo_clicked)
            else:
                FreeCAD.Console.PrintWarning("El botón 'btnEjemplo' no se encontró en la UI.\n")
        except Exception as e:
            FreeCAD.Console.PrintError(f"Error al configurar conexiones: {str(e)}\n")

    def on_btnEjemplo_clicked(self):
        """
        Ejemplo de función que responde al clic de un botón.
        """
        FreeCAD.Console.PrintMessage("¡Botón clickeado!\n")

# Comprobar si la aplicación se ejecuta dentro de FreeCAD
if FreeCADGui:
    try:
        app = DiagramaUnifilarApp()
        app.show()
    except Exception as e:
        FreeCAD.Console.PrintError(f"Error al inicializar la aplicación: {str(e)}\n")
