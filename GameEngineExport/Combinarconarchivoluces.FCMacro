# Macro: CombinarLucesEdificio.FCMacro
# Descripcion:
# Permite seleccionar mediante un dialogo de archivos el modelo de edificio y el modelo de luces, y guarda el archivo X3D combinado.
# Autor: GPT + Usuario
# Fecha: 2025-07-12

import os
import FreeCAD
import FreeCADGui
from PySide import QtWidgets


def combine_x3d():
    # Dialogo para seleccionar archivo de edificio
    edificio_path, filtro1 = QtWidgets.QFileDialog.getOpenFileName(
        None,
        "Seleccionar archivo de edificio",
        "",
        "X3D Files (*.x3d);;Collada Files (*.dae)"
    )
    if not edificio_path:
        FreeCAD.Console.PrintMessage("Operacion cancelada: no se selecciono archivo de edificio.\n")
        return

    # Dialogo para seleccionar archivo de luces
    luces_path, filtro2 = QtWidgets.QFileDialog.getOpenFileName(
        None,
        "Seleccionar archivo de luces",
        "",
        "X3D Files (*.x3d)"
    )
    if not luces_path:
        FreeCAD.Console.PrintMessage("Operacion cancelada: no se selecciono archivo de luces.\n")
        return

    # Dialogo para guardar archivo combinado
    salida_path, filtro3 = QtWidgets.QFileDialog.getSaveFileName(
        None,
        "Guardar archivo combinado",
        "Puriscal_con_luces.x3d",
        "X3D Files (*.x3d)"
    )
    if not salida_path:
        FreeCAD.Console.PrintMessage("Operacion cancelada: no se selecciono destino de guardado.\n")
        return

    # Leer contenido de edificio y luces
    with open(edificio_path, 'r', encoding='utf-8') as f:
        contenido_edificio = f.read()
    with open(luces_path, 'r', encoding='utf-8') as f:
        contenido_luces = f.read()

    # Extraer nodos de luces dentro de <Scene>...
    inicio = contenido_luces.find('<Scene>') + len('<Scene>')
    fin = contenido_luces.find('</Scene>')
    luces_snippet = contenido_luces[inicio:fin].strip()

    # Insertar antes de </Scene> del edificio
    idx_final = contenido_edificio.rfind('</Scene>')
    combinado = (
        contenido_edificio[:idx_final].rstrip() +
        "\n  <!-- Luces insertadas -->\n  " + luces_snippet +
        "\n" + contenido_edificio[idx_final:]
    )

    # Guardar archivo combinado
    with open(salida_path, 'w', encoding='utf-8') as f:
        f.write(combinado)

    FreeCAD.Console.PrintMessage(f"Archivo combinado guardado en: {salida_path}\n")

# Ejecutar la función
combine_x3d()
