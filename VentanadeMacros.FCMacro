# -*- coding: utf-8 -*-
"""
Macro: MacroRunnerDialog
Descripcion: Ventana para buscar y ejecutar macros.
- Permite buscar y ejecutar macros desde el directorio de macros.
- Agrupa macros por subdirectorios.
- Guarda lista de macros recientes.
- Evita multiples instancias de la ventana.
- Guarda posicion y tamano de la ventana.
- Carga icono SVG si esta disponible.

Fecha: 2025-02-19
Autor: [Tu Nombre]

Genera: Una interfaz grafica en FreeCAD para ejecutar macros.
"""

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

import FreeCAD
import FreeCADGui
import os
from functools import partial
from PySide2 import QtGui, QtCore, QtWidgets

_RESOLVE_CACHE = {}
_SEARCH_PREFIXES = ("", "Macros-de-Freecad", os.path.join("Macros-de-Freecad", "Resources"))


def _macro_path_entries():
    param = FreeCAD.ParamGet("User parameter:BaseApp/Preferences/Macro").GetString("MacroPath", "")
    entries = []
    if param:
        sep = ";" if os.name == "nt" else ":"
        for part in param.split(sep):
            part = part.strip()
            if part:
                full = os.path.normpath(os.path.abspath(part))
                if full not in entries:
                    entries.append(full)
    try:
        user_dir = FreeCAD.getUserMacroDir()
    except Exception:
        user_dir = ""
    if user_dir:
        full = os.path.normpath(os.path.abspath(user_dir))
        if full not in entries:
            entries.append(full)
    return entries


def _search_roots():
    roots = []
    seen = set()
    for base in _macro_path_entries():
        for extra in _SEARCH_PREFIXES:
            candidate = os.path.join(base, extra) if extra else base
            candidate = os.path.normpath(candidate)
            if candidate not in seen:
                roots.append(candidate)
                seen.add(candidate)
    return roots


def _candidate_relpaths(rel):
    rel = rel.replace("\\", "/")
    parts = [p for p in rel.split("/") if p and p != "."]
    variants = []

    def add(parts_list):
        if not parts_list:
            return
        candidate = os.path.join(*parts_list)
        if candidate not in variants:
            variants.append(candidate)

    if parts:
        add(parts)
        if parts[0].lower() == "macros-de-freecad":
            add(parts[1:])
            add(["Macros-de-Freecad", "Resources"] + parts[1:])
        else:
            add(["Macros-de-Freecad"] + parts)
            add(["Macros-de-Freecad", "Resources"] + parts)
        if parts[0].lower() == "resources":
            add(parts[1:])
        else:
            add(["Resources"] + parts)
    return [v for v in variants if v]


def _resolve_macro_path(path):
    if not path:
        return path
    norm = os.path.normpath(path)
    key = os.path.normcase(norm)
    cached = _RESOLVE_CACHE.get(key)
    if cached:
        return cached
    if os.path.exists(norm):
        _RESOLVE_CACHE[key] = norm
        return norm
    for base in _macro_path_entries():
        try:
            rel = os.path.relpath(norm, base)
        except Exception:
            continue
        if rel.startswith(".."):
            continue
        for candidate_rel in _candidate_relpaths(rel):
            candidate = os.path.normpath(os.path.join(base, candidate_rel))
            if os.path.exists(candidate):
                _RESOLVE_CACHE[key] = candidate
                return candidate
    filename = os.path.basename(norm)
    for root in _search_roots():
        if not os.path.isdir(root):
            continue
        for dirpath, _, files in os.walk(root):
            if filename in files:
                resolved = os.path.normpath(os.path.join(dirpath, filename))
                _RESOLVE_CACHE[key] = resolved
                return resolved
    _RESOLVE_CACHE[key] = norm
    return norm


def _macro_display_label(base, rel):
    base_name = os.path.basename(base.rstrip("\\/"))
    rel_norm = rel.replace("\\", "/")
    parts = [p for p in rel_norm.split("/") if p and p != "."]
    if parts:
        label = "/".join(parts)
        return f"{base_name}/{label}" if base_name else label
    return base_name or os.path.normpath(base)


class MacroRunnerDialog(QtWidgets.QDialog):
    instance = None

    def __init__(self, parent=None):
        super(MacroRunnerDialog, self).__init__(parent)
        self.setWindowTitle("Macro Runner")
        self.setMinimumWidth(600)

        self.set_window_icon()
        self.load_window_settings()

        layout = QtWidgets.QVBoxLayout(self)

        self.search_input = QtWidgets.QLineEdit()
        self.search_input.setPlaceholderText("Buscar macro...")
        self.search_input.textChanged.connect(self.update_macro_list)
        layout.addWidget(self.search_input)

        self.update_button = QtWidgets.QPushButton("Actualizar macros")
        self.update_button.clicked.connect(self.update_macro_list)
        layout.addWidget(self.update_button)

        self.scroll_area = QtWidgets.QScrollArea()
        self.scroll_area.setWidgetResizable(True)
        self.scroll_widget = QtWidgets.QWidget()
        self.scroll_layout = QtWidgets.QGridLayout(self.scroll_widget)
        self.scroll_area.setWidget(self.scroll_widget)
        self.scroll_area.setMinimumHeight(250)
        layout.addWidget(self.scroll_area)

        self.recent_macros_label = QtWidgets.QLabel("Macros Usadas Recientemente")
        layout.addWidget(self.recent_macros_label)
        self.recent_macros_list = QtWidgets.QListWidget()
        self.recent_macros_list.setMaximumHeight(100)
        layout.addWidget(self.recent_macros_list)

        botones = QtWidgets.QDialogButtonBox(QtWidgets.QDialogButtonBox.Ok | QtWidgets.QDialogButtonBox.Cancel)
        layout.addWidget(botones)
        botones.accepted.connect(self.accept)
        botones.rejected.connect(self.reject)

        self.setLayout(layout)

        self.update_macro_list()
        self.load_recent_macros()

    def set_window_icon(self):
        icon_name = "Ventana de Macros.svg"
        candidates = []
        for root in _search_roots():
            for sub in ("iconos", "", os.path.join("Resources", "iconos")):
                candidate = os.path.join(root, sub, icon_name) if sub else os.path.join(root, icon_name)
                candidate = os.path.normpath(candidate)
                if candidate not in candidates:
                    candidates.append(candidate)
        for icon_path in candidates:
            if os.path.exists(icon_path):
                self.setWindowIcon(QtGui.QIcon(icon_path))
                FreeCAD.Console.PrintMessage(f"Icono cargado desde: {icon_path}\n")
                return
        FreeCAD.Console.PrintWarning("No se encontro 'Ventana de Macros.svg' en los directorios de iconos.\n")

    def update_macro_list(self):
        FreeCAD.Console.PrintMessage("Actualizando lista de macros...\n")
        for i in reversed(range(self.scroll_layout.count())):
            item = self.scroll_layout.itemAt(i)
            widget = item.widget() if item else None
            if widget is not None:
                widget.deleteLater()

        macro_roots = _search_roots()
        if not macro_roots:
            FreeCAD.Console.PrintError("El directorio de macros no esta configurado.\n")
            return

        macros_by_category = []
        seen = set()
        for base in macro_roots:
            if not os.path.isdir(base):
                continue
            for root, _, files in os.walk(base):
                macro_files = [f for f in files if f.lower().endswith(".fcmacro")]
                if not macro_files:
                    continue
                macros = []
                for file in sorted(macro_files):
                    full = os.path.normpath(os.path.join(root, file))
                    normcase = os.path.normcase(full)
                    if normcase in seen:
                        continue
                    seen.add(normcase)
                    macros.append(full)
                if macros:
                    rel = os.path.relpath(root, base)
                    macros_by_category.append((base, rel, macros))

        if not macros_by_category:
            FreeCAD.Console.PrintWarning("No se encontraron macros en los directorios configurados.\n")
            return

        macros_by_category.sort(key=lambda item: _macro_display_label(item[0], item[1]).lower())

        col = 0
        for base, rel, macros in macros_by_category:
            label_text = _macro_display_label(base, rel)
            category_label = QtWidgets.QLabel(label_text)
            category_label.setStyleSheet("font-weight: bold;")
            self.scroll_layout.addWidget(category_label, 0, col)
            row = 1
            for macro in macros:
                name = os.path.splitext(os.path.basename(macro))[0]
                button = QtWidgets.QPushButton(name)
                button.setToolTip(macro)
                button.clicked.connect(partial(self.run_macro, macro))
                self.scroll_layout.addWidget(button, row, col)
                row += 1
            col += 1

    def run_macro(self, macro):
        target = _resolve_macro_path(macro)
        try:
            if not os.path.exists(target):
                raise FileNotFoundError(f"No se encontro la macro: {target}")
            with open(target, "r", encoding="utf-8", errors="ignore") as handle:
                exec(handle.read(), globals())
            self.add_to_recent_macros(target)
        except Exception as exc:
            FreeCAD.Console.PrintError(f"Error ejecutando la macro: {exc}\n")

    def add_to_recent_macros(self, macro):
        settings = QtCore.QSettings("FreeCAD", "MacroRunner")
        resolved = _resolve_macro_path(macro)
        recent = settings.value("recent_macros", []) or []
        if resolved in recent:
            recent.remove(resolved)
        recent.insert(0, resolved)
        recent = [r for r in recent if os.path.exists(r)]
        settings.setValue("recent_macros", recent[:10])
        self.load_recent_macros()

    def load_recent_macros(self):
        settings = QtCore.QSettings("FreeCAD", "MacroRunner")
        stored = settings.value("recent_macros", []) or []
        resolved_list = []
        changed = False
        for macro in stored:
            resolved = _resolve_macro_path(macro)
            if resolved != macro:
                changed = True
            if os.path.exists(resolved) and resolved not in resolved_list:
                resolved_list.append(resolved)
        if changed or len(resolved_list) != len(stored):
            settings.setValue("recent_macros", resolved_list[:10])
        self.recent_macros_list.clear()
        for macro in resolved_list:
            self.recent_macros_list.addItem(macro)

    def load_window_settings(self):
        settings = QtCore.QSettings("FreeCAD", "MacroRunner")
        self.resize(settings.value("window_size", QtCore.QSize(600, 400)))
        self.move(settings.value("window_position", QtCore.QPoint(200, 200)))

    def closeEvent(self, event):
        settings = QtCore.QSettings("FreeCAD", "MacroRunner")
        settings.setValue("window_size", self.size())
        settings.setValue("window_position", self.pos())
        MacroRunnerDialog.instance = None
        super().closeEvent(event)


if MacroRunnerDialog.instance is None:
    MacroRunnerDialog.instance = MacroRunnerDialog()
    MacroRunnerDialog.instance.show()
else:
    MacroRunnerDialog.instance.raise_()
    MacroRunnerDialog.instance.activateWindow()
