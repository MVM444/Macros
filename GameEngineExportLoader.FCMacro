# -*- coding: utf-8 -*-
# Icon: GameEngineExportLoader.svg
# GameEngineExportLoader Macro
# Description: Reload and activate GameEngineExportWB from the Macros-de-Freecad repo.
# Notes: Uses hot-reload flow (close panel + purge commands/modules + re-register workbench).
# Version: 2026-07-27

import importlib
import os
import sys

import FreeCAD as App
import FreeCADGui as Gui


LOG_PREFIX = "[GAMEEXPORT] "
WB_CANDIDATES = ("GameEngineExportWorkbench", "Game Engine Export WB", "GameEngineExportWB")
MODULE_PREFIXES = ("GameEngineExportWB", "Mod.GameEngineExportWB")
MODULE_CANDIDATES = ("GameEngineExportWB.InitGui", "Mod.GameEngineExportWB.InitGui")
COMMAND_CANDIDATES = (
    "GameEngineExport_Open",
    "GameEngineExport_Export",
    "GameEngineExport_Export_Current",
    "GameEngineExport_Config",
    "GameEngineExport_AddLightProperties",
    "GameEngineExport_QuickExample",
)
LOADER_MENU_TEXT = "Game Engine Export Loader"
LOADER_TOOLTIP = "Carga y recarga el workbench Game Engine Export"


def log_info(message):
    App.Console.PrintMessage(LOG_PREFIX + str(message) + "\n")


def log_error(message):
    App.Console.PrintError(LOG_PREFIX + str(message) + "\n")


def install_loader_toolbar():
    here = os.path.normpath(os.path.abspath(os.path.dirname(__file__)))
    helper_roots = (os.path.join(here, "Macros-de-Freecad"), here)
    for root in helper_roots:
        if os.path.exists(os.path.join(root, "loader_toolbar.py")) and root not in sys.path:
            sys.path.insert(0, root)
    try:
        from loader_toolbar import install_global_loader_toolbar

        return install_global_loader_toolbar(
            App,
            Gui,
            __file__,
            os.path.join(here, "GameEngineExportLoader.svg"),
            LOADER_MENU_TEXT,
            LOADER_TOOLTIP,
            LOG_PREFIX,
        )
    except Exception as exc:
        log_error("Could not install global loader toolbar: " + str(exc))
        return None


def normalize_path(path_text):
    return os.path.normcase(os.path.normpath(os.path.abspath(path_text)))


def ensure_repo_on_path(repo_root):
    repo_root = os.path.normpath(os.path.abspath(repo_root))
    normalized = normalize_path(repo_root)
    old_count = len(sys.path)
    sys.path[:] = [path for path in sys.path if normalize_path(path or os.getcwd()) != normalized]
    removed = old_count - len(sys.path)
    sys.path.insert(0, repo_root)
    if removed:
        log_info("Moved repo path to front: " + repo_root)
    else:
        log_info("Added repo path at front: " + repo_root)


def candidate_repo_roots():
    here = os.path.dirname(__file__)
    roots = []
    for root in (os.path.join(here, "Macros-de-Freecad"), here):
        root = os.path.normpath(os.path.abspath(root))
        if os.path.isdir(root) and root not in roots:
            roots.append(root)
    return roots


def purge_modules():
    removed = 0
    for name in list(sys.modules.keys()):
        name_l = str(name).lower()
        if any(name == prefix or name.startswith(prefix + ".") for prefix in MODULE_PREFIXES) or "gameengineexportwb" in name_l:
            sys.modules.pop(name, None)
            removed += 1
    log_info("Purged modules: " + str(removed))


def stop_active_web_preview():
    """Stop a preview HTTP server before its module is removed."""
    stopped_modules = set()
    for name, module in list(sys.modules.items()):
        name_l = str(name).lower()
        if not name_l.endswith(".core.web_preview") or module is None:
            continue
        module_id = id(module)
        if module_id in stopped_modules:
            continue
        stopped_modules.add(module_id)
        stop_server = getattr(module, "stop_preview_server", None)
        if not callable(stop_server):
            continue
        try:
            stop_server("Workbench hot restart")
            log_info("Stopped active Web preview server")
        except Exception as exc:
            log_error("Could not stop Web preview server: " + str(exc))


def close_active_dialog():
    try:
        control = getattr(Gui, "Control", None)
        if control is not None and hasattr(control, "activeDialog") and control.activeDialog():
            control.closeDialog()
            log_info("Closed active task dialog")
    except Exception as exc:
        log_error("Could not close active task dialog: " + str(exc))


def deactivate_workbench():
    for wb_name in ("StartWorkbench", "NoneWorkbench"):
        try:
            Gui.activateWorkbench(wb_name)
            log_info("Activated neutral workbench: " + wb_name)
            return
        except Exception:
            pass


def remove_old_commands():
    if not hasattr(Gui, "removeCommand"):
        log_info("removeCommand not available in this FreeCAD build")
        return
    command_names = set(COMMAND_CANDIDATES)
    try:
        for command_name in getattr(Gui, "listCommands", lambda: [])() or []:
            if str(command_name).startswith("GameEngineExport_"):
                command_names.add(str(command_name))
    except Exception:
        pass
    removed = 0
    for command_name in sorted(command_names):
        try:
            Gui.removeCommand(command_name)
            removed += 1
            log_info("Removed command: " + command_name)
        except Exception:
            pass
    log_info("Removed commands: " + str(removed))


def remove_old_workbench():
    try:
        workbenches = dict(getattr(Gui, "listWorkbenches", lambda: {})() or {})
    except Exception:
        workbenches = {}

    if not hasattr(Gui, "removeWorkbench"):
        return

    deactivate_workbench()

    names_to_remove = set(WB_CANDIDATES)
    for existing_name in workbenches.keys():
        if "gameengineexport" in str(existing_name).lower():
            names_to_remove.add(existing_name)

    for wb_name in names_to_remove:
        if wb_name in workbenches:
            try:
                Gui.removeWorkbench(wb_name)
                log_info("Removed previous workbench: " + wb_name)
            except Exception as exc:
                log_error("Could not remove workbench " + wb_name + ": " + str(exc))


def import_workbench_initgui():
    last_error = None
    for module_name in MODULE_CANDIDATES:
        try:
            module = importlib.import_module(module_name)
            importlib.reload(module)
            log_info("Loaded InitGui from: " + str(getattr(module, "__file__", "unknown")))
            return module
        except Exception as exc:
            last_error = exc
    if last_error:
        raise last_error
    raise RuntimeError("No GameEngineExport InitGui module candidate was attempted")


def activate_workbench():
    last_error = None
    for wb_name in WB_CANDIDATES:
        try:
            Gui.activateWorkbench(wb_name)
            log_info("Activated workbench: " + wb_name)
            return
        except Exception as exc:
            last_error = exc
    if last_error:
        raise last_error
    raise RuntimeError("No GameEngineExport workbench candidate was attempted")


def main():
    toolbar_handle = install_loader_toolbar()
    log_info("Hot restart requested")
    close_active_dialog()
    repo_roots = candidate_repo_roots()
    for repo_root in reversed(repo_roots):
        ensure_repo_on_path(repo_root)
    deactivate_workbench()
    remove_old_workbench()
    remove_old_commands()
    stop_active_web_preview()
    purge_modules()
    importlib.invalidate_caches()
    import_workbench_initgui()
    activate_workbench()
    try:
        if hasattr(Gui, "updateGui"):
            Gui.updateGui()
    except Exception:
        pass
    if toolbar_handle is not None:
        toolbar_handle.refresh()
    log_info("Workbench hot restart completed")


if __name__ == "__main__":
    try:
        main()
    except Exception as exc:
        log_error("Failed to load workbench: " + str(exc))
        raise
