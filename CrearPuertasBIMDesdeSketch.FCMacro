"""Crear puertas BIM desde el sketch seleccionado.

Seleccione un Sketch con lineas de centro de buques de puerta y ejecute la macro.
Las hojas de puerta se generan abiertas a 90 grados.
"""

from __future__ import annotations

import os
import runpy

import FreeCAD


HELPER = os.path.join(
    os.path.dirname(__file__),
    "Macros-de-Freecad",
    "GameEngineExportWB",
    "macros",
    "bim_from_selected_sketch.py",
)

if not os.path.exists(HELPER):
    raise RuntimeError("No se encontro helper BIM desde sketch: " + HELPER)

namespace = runpy.run_path(HELPER)
FreeCAD.Console.PrintMessage("[BIM-SKETCH] Ejecutando puertas desde sketch seleccionado\n")
namespace["run"]("doors")
