# -*- coding: utf-8 -*-
# MenuText: FA Poligonos de recintos desde muros BIM
# ToolTip: Crea areas poligonales exactas desde huecos cerrados de Arch Walls.
# Icon: FacilArquitecturaLoader.svg

"""Compatibility launcher for the independent polygonal-room macro."""

from __future__ import annotations

import os


MACRO_DIR = os.path.normpath(os.path.abspath(os.path.dirname(__file__)))
ENGINE = os.path.join(
    MACRO_DIR,
    "Macros-de-Freecad",
    "Areas",
    "PoligonosRecintosDesdeArchWalls.FCMacro",
)

if not os.path.isfile(ENGINE):
    raise RuntimeError("No se encontro la macro de poligonos: " + ENGINE)

namespace = {"__name__": "__main__", "__file__": ENGINE}
with open(ENGINE, "rb") as stream:
    exec(compile(stream.read(), ENGINE, "exec"), namespace)
