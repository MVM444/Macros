#!/usr/bin/env python
# -*- coding: utf-8 -*-
# ============================================================================
# Tomacorriente hibrido 2D+3D con conmutador de visibilidad
# Proyecto: Programacion en FreeCAD - Objetos 3D con proyeccion en planta
# Archivo: Insertar_Tomacorriente_2D-3D.FCMacro
# Version: 2025-09-15 14:00
#
# Descripcion:
# - Objeto hibrido que combina simbolo 2D y modelo 3D.
# - Propiedad ModoVisual: "Ambos", "Solo2D", "Solo3D".
# - Transformaciones via Placement/AttachmentOffset: Altura (Z), Giro (deg),
#   OffsetX/OffsetY (plano local).
# - Colocacion por seleccion usando Attachment (cara/borde), para que el objeto
#   siga la referencia si la pared o borde cambian.
#
# Notas clave del proyecto:
# - No usar acentos ni caracteres especiales en codigo/comentarios/strings.
# - Mostrar depuracion en consola.
# - Las macros residen en el directorio de macros de FreeCAD o subdirectorios.
# - Objetivo final: consolidar en un Workbench con macros funcionales.
#
# Recursos esperados:
#   Resources/SimboloToma.step
#   Resources/tomacorriente-3D.step
#
# Logs:
#   [TOMA23D][INFO] ...
#   [TOMA23D][WARN] ...
#   [TOMA23D][ERROR] ...
# ============================================================================

import FreeCAD as App
import FreeCADGui as Gui
import Part
import os
from math import atan2, degrees

LOG_TAG = "[TOMA23D]"

def _print_info(msg):
    App.Console.PrintMessage(f"{LOG_TAG}[INFO] {msg}\n")

def _print_warn(msg):
    App.Console.PrintWarning(f"{LOG_TAG}[WARN] {msg}\n")

def _print_err(msg):
    App.Console.PrintError(f"{LOG_TAG}[ERROR] {msg}\n")


class TomacorrienteHibrido(object):
    """
    Objeto 2D+3D con conmutador de visibilidad y manipulacion por Placement.
    Propiedades:
      - ModoVisual: "Ambos" | "Solo2D" | "Solo3D"
      - Altura (mm): aplica a Z mediante Placement/AttachmentOffset
      - Giro (deg): rotacion alrededor de Z local
      - OffsetX/OffsetY (mm): traslaciones locales en XY
    """

    def __init__(self, obj):
        grp = "Tomacorriente"
        # cache de shapes por instancia
        self._s2d = None
        self._s3d = None

        obj.addProperty("App::PropertyEnumeration", "ModoVisual", grp, "Controla que se muestra").ModoVisual = ["Ambos", "Solo2D", "Solo3D"]
        obj.ModoVisual = "Ambos"

        obj.addProperty("App::PropertyLength", "Altura", grp, "Altura Z del componente").Altura = 300
        obj.addProperty("App::PropertyAngle", "Giro", grp, "Giro en el plano (deg)").Giro = 0.0
        obj.addProperty("App::PropertyLength", "OffsetX", grp, "Desplazamiento local X").OffsetX = 0
        obj.addProperty("App::PropertyLength", "OffsetY", grp, "Desplazamiento local Y").OffsetY = 0

        # opcional: versionado simple para futuras migraciones
        obj.addProperty("App::PropertyString", "SchemaVersion", grp, "Version interna de esquema").SchemaVersion = "2025-09-15T14:00Z"

        # nombres de representaciones hijas
        obj.addProperty("App::PropertyString", "Rep2DName", grp, "Nombre del objeto hijo 2D").Rep2DName = "Rep2D"
        obj.addProperty("App::PropertyString", "Rep3DName", grp, "Nombre del objeto hijo 3D").Rep3DName = "Rep3D"

        obj.Proxy = self

    # -------------------------
    # Resolucion de rutas
    # -------------------------
    def _resource_dirs(self):
        dirs = []

        # 1) Directorio de este archivo (si disponible)
        try:
            here = os.path.dirname(os.path.abspath(__file__))
            dirs.append(os.path.join(here, "Resources"))
            # Nuevo: tambien considerar Resources en el directorio padre del macro
            parent = os.path.abspath(os.path.join(here, os.pardir))
            dirs.append(os.path.join(parent, "Resources"))
        except Exception:
            pass

        # 2) Directorio de macros del usuario
        try:
            udir = App.getUserMacroDir()
            if udir:
                dirs.append(os.path.join(udir, "Resources"))
        except Exception:
            pass

        # 3) MacroPath puede tener multiples entradas separadas por ; o :
        try:
            sep = ";" if os.name == "nt" else ":"
            mp = App.ParamGet("User parameter:BaseApp/Preferences/Macro").GetString("MacroPath", "")
            for p in mp.split(sep):
                p = p.strip()
                if p:
                    dirs.append(os.path.join(p, "Resources"))
        except Exception:
            pass

        # quitar duplicados preservando orden
        seen = set()
        unique_dirs = []
        for d in dirs:
            if d not in seen:
                unique_dirs.append(d)
                seen.add(d)
        return unique_dirs

    def _rutas(self):
        def pick_3d_step(dirpath):
            # Preferencia por nombres esperados, con fallback por coincidencia parcial
            candidates = [
                os.path.join(dirpath, "tomacorriente-3D.step"),
                os.path.join(dirpath, "Tomacorriente-3d.step"),
                os.path.join(dirpath, "Tomacorriente-3d - copia.step"),
            ]
            for c in candidates:
                if os.path.exists(c):
                    return c
            try:
                for fn in os.listdir(dirpath):
                    if not fn.lower().endswith((".step", ".stp")):
                        continue
                    if "tomacorriente" in fn.lower():
                        return os.path.join(dirpath, fn)
            except Exception:
                pass
            return None

        for d in self._resource_dirs():
            a2 = os.path.join(d, "SimboloToma.step")
            a3 = pick_3d_step(d)
            if os.path.exists(a2) and a3 and os.path.exists(a3):
                _print_info(f"Usando recursos: 2D='{os.path.basename(a2)}', 3D='{os.path.basename(a3)}' en '{d}'")
                return a2, a3
        _print_err("Resources not found: expected 'Resources/SimboloToma.step' and a 3D STEP for tomacorriente")
        return None, None

    def _cargar_shapes(self):
        if self._s2d is not None and self._s3d is not None:
            return self._s2d, self._s3d
        a2, a3 = self._rutas()
        if not a2 or not a3:
            return None, None
        try:
            s2d = Part.Shape(); s2d.read(a2)
            s3d = Part.Shape(); s3d.read(a3)
            self._s2d, self._s3d = s2d, s3d
            _print_info("Shapes loaded from Resources")
        except Exception as e:
            _print_err(f"Error reading STEP: {e}")
            return None, None
        return self._s2d, self._s3d

    def _get_child_by_label(self, obj, label):
        try:
            for ch in getattr(obj, 'Group', []):
                if ch.Label == label or ch.Name == label:
                    return ch
        except Exception:
            pass
        return None

    def _ensure_reps(self, obj):
        """Asegura objetos hijos Rep2D y Rep3D con sus shapes y pertenencia al grupo."""
        s2d, s3d = self._cargar_shapes()
        if not s2d or not s3d:
            return None, None

        rep2d = self._get_child_by_label(obj, getattr(obj, 'Rep2DName', 'Rep2D'))
        rep3d = self._get_child_by_label(obj, getattr(obj, 'Rep3DName', 'Rep3D'))

        doc = obj.Document
        if rep2d is None and doc is not None:
            rep2d = doc.addObject("Part::Feature", getattr(obj, 'Rep2DName', 'Rep2D'))
            rep2d.Label = getattr(obj, 'Rep2DName', 'Rep2D')
            rep2d.Shape = s2d.copy()
            try:
                obj.addObject(rep2d)
            except Exception:
                pass
        elif rep2d is not None and rep2d.Shape.isNull():
            rep2d.Shape = s2d.copy()

        if rep3d is None and doc is not None:
            rep3d = doc.addObject("Part::Feature", getattr(obj, 'Rep3DName', 'Rep3D'))
            rep3d.Label = getattr(obj, 'Rep3DName', 'Rep3D')
            rep3d.Shape = s3d.copy()
            try:
                obj.addObject(rep3d)
            except Exception:
                pass
        elif rep3d is not None and rep3d.Shape.isNull():
            rep3d.Shape = s3d.copy()

        return rep2d, rep3d

    # -------------------------
    # Ejecucion y actualizacion
    # -------------------------
    def execute(self, obj):
        # Asegurar representaciones y actualizar visibilidad/placements.
        rep2d, rep3d = self._ensure_reps(obj)
        if rep2d is None or rep3d is None:
            return
        self._apply_transform(obj)
        self._apply_visibility(obj)

    def _apply_transform(self, obj):
        """Coloca 2D en plano de trabajo y 3D a la altura correcta.
        - 2D: en el WorkingPlane (Draft), con Giro/Offset en XY local.
        - 3D: orientado segun obj.Placement (por seleccion) y trasladado +Altura en Z local.
        """
        try:
            offx = getattr(obj.OffsetX, 'Value', 0.0)
            offy = getattr(obj.OffsetY, 'Value', 0.0)
            alt  = getattr(obj.Altura, 'Value', 0.0)
            rot  = float(obj.Giro)

            # buscar hijos
            rep2d = self._get_child_by_label(obj, getattr(obj, 'Rep2DName', 'Rep2D'))
            rep3d = self._get_child_by_label(obj, getattr(obj, 'Rep3DName', 'Rep3D'))

            # 2D en plano de trabajo
            if rep2d is not None:
                wp_pl = App.Placement()
                try:
                    import Draft  # disponible en GUI
                    wp = Draft.getWorkingPlane()
                    wp_pl = wp.getPlacement()
                except Exception:
                    # fallback: plano XY global
                    wp_pl = App.Placement()

                # proyectar base global del objeto al sistema del WP para conservar XY
                base_glob = obj.Placement.Base
                try:
                    loc = wp_pl.inverse().multVec(base_glob)
                    loc_xy = App.Vector(loc.x + offx, loc.y + offy, 0)
                except Exception:
                    loc_xy = App.Vector(offx, offy, 0)

                local_off = App.Placement(loc_xy, App.Rotation(App.Vector(0, 0, 1), rot))
                rep2d.Placement = wp_pl.multiply(local_off)

            # 3D orientado por seleccion, altura en Z local
            if rep3d is not None:
                # Colocar 3D con orientacion de la seleccion, pero altura en Z global
                base = obj.Placement.Base
                base_alt = App.Vector(base.x, base.y, alt)
                rep3d.Placement = App.Placement(base_alt, obj.Placement.Rotation)

        except Exception as e:
            _print_err(f"apply_transform failed: {e}")

    def _apply_visibility(self, obj):
        try:
            modo = str(obj.ModoVisual)
            rep2d = self._get_child_by_label(obj, getattr(obj, 'Rep2DName', 'Rep2D'))
            rep3d = self._get_child_by_label(obj, getattr(obj, 'Rep3DName', 'Rep3D'))
            if rep2d is None or rep3d is None:
                return
            if modo == "Ambos":
                rep2d.ViewObject.Visibility = True
                rep3d.ViewObject.Visibility = True
            elif modo == "Solo2D":
                rep2d.ViewObject.Visibility = True
                rep3d.ViewObject.Visibility = False
            elif modo == "Solo3D":
                rep2d.ViewObject.Visibility = False
                rep3d.ViewObject.Visibility = True
        except Exception as e:
            _print_warn(f"visibility apply issue: {e}")

    def onChanged(self, obj, prop):
        # cambios que afectan solo Placement/Attachment
        if prop in ("Altura", "Giro", "OffsetX", "OffsetY", "Placement"):
            self._apply_transform(obj)
            try:
                obj.touch()
                if obj.Document:
                    obj.Document.recompute()
            except Exception:
                pass
            return

        # cambios que afectan el contenido de Shape
        if prop in ("ModoVisual",):
            try:
                self._apply_visibility(obj)
                obj.touch()
                if obj.Document:
                    obj.Document.recompute()
            except Exception:
                pass


class ViewProviderTomacorrienteHibrido(object):
    def __init__(self, vobj):
        vobj.Proxy = self
        self.Object = vobj.Object

    def getDefaultDisplayMode(self):
        return "Flat Lines"

    def attach(self, vobj):
        self.Object = vobj.Object

    def __getstate__(self):
        return None

    def __setstate__(self, state):
        return None

    # Opcional: ajustar estilo segun modo para lectura
    def updateVisual(self):
        try:
            vobj = self.Object.ViewObject
            modo = str(self.Object.ModoVisual)
            if modo == "Ambos":
                vobj.Transparency = 70
                vobj.LineWidth = 1.0
            elif modo == "Solo2D":
                vobj.Transparency = 0
                vobj.LineWidth = 2.0
            elif modo == "Solo3D":
                vobj.Transparency = 0
                vobj.LineWidth = 1.0
        except Exception as e:
            _print_warn(f"updateVisual issue: {e}")


# -------------------------
# Colocacion por seleccion
# -------------------------
def _attach_by_selection(obj):
    """Coloca por seleccion (cara/borde) ajustando Placement, sin Attachment."""
    try:
        if not App.GuiUp:
            return
        sel = Gui.Selection.getSelectionEx()
        if not sel:
            return

        s = sel[0]
        if not s.HasSubObjects or not s.SubElementNames:
            return

        # Usar Placement directo para evitar dependencias de Attachment
        sub = s.SubObjects[0]
        if isinstance(sub, Part.Face):
            try:
                n = sub.normalAt(0.5, 0.5)
                base = sub.CenterOfMass
                # orientar Z global a Z de la cara: usar dos vectores
                rot = App.Rotation(App.Vector(0, 0, 1), n)
                pl = obj.Placement
                pl.Rotation = rot
                pl.Base = base
                obj.Placement = pl
            except Exception as e:
                _print_warn(f"face placement failed: {e}")
        else:
            try:
                par = 0.5
                if hasattr(sub, 'FirstParameter') and hasattr(sub, 'LastParameter'):
                    par = 0.5 * (sub.FirstParameter + sub.LastParameter)
                tan = sub.tangentAt(par)
            except Exception:
                tan = App.Vector(1, 0, 0)
            tan2d = App.Vector(tan.x, tan.y, 0)
            if tan2d.Length == 0:
                tan2d = App.Vector(1, 0, 0)
            ang_deg = degrees(atan2(tan2d.y, tan2d.x))
            try:
                base = sub.CenterOfMass
            except Exception:
                try:
                    base = sub.valueAt(0.5)
                except Exception:
                    base = App.Vector(0, 0, 0)
            pl = obj.Placement
            pl.Rotation = App.Rotation(App.Vector(0, 0, 1), ang_deg)
            pl.Base = base
            obj.Placement = pl

    except Exception as e:
        _print_err(f"_attach_by_selection error: {e}")


# -------------------------
# Creacion del objeto
# -------------------------
def crear_tomacorriente_hibrido():
    doc = App.ActiveDocument or App.newDocument("PlanoElectricos")
    obj = doc.addObject("Part::FeaturePython", "TomacorrienteHibrido")
    # add grouping extension only
    try:
        obj.addExtension("App::GroupExtensionPython")
    except Exception:
        pass
    proxy = TomacorrienteHibrido(obj)
    vp = ViewProviderTomacorrienteHibrido(obj.ViewObject)

    # colocar por seleccion para orientar el objeto (para 3D)
    _attach_by_selection(obj)

    # crear representaciones y aplicar transformaciones/visibilidad iniciales
    proxy._ensure_reps(obj)
    proxy._apply_transform(obj)
    proxy._apply_visibility(obj)

    doc.recompute()
    vp.updateVisual()

    # Ocultar el contenedor padre (solo se muestran hijos Rep2D/Rep3D)
    try:
        obj.ViewObject.Visibility = False
    except Exception:
        pass

    _print_info("Tomacorriente hibrido creado. Cambia 'ModoVisual' en Propiedades.")


# Ejecutar creacion
crear_tomacorriente_hibrido()
