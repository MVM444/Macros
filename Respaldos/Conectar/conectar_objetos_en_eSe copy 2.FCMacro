import FreeCAD
import FreeCADGui
import Part
import Draft
import math

def conectar_objetos_en_eSe():
    doc = FreeCAD.ActiveDocument
    selected_objects = FreeCADGui.Selection.getSelectionEx()

    if len(selected_objects) != 2:
        FreeCAD.Console.PrintError("Debe seleccionar exactamente dos objetos (aristas o caras).\n")
        return

    FreeCAD.Console.PrintMessage(f"Objetos seleccionados: {selected_objects[0].Object.Name}, {selected_objects[1].Object.Name}\n")

    def obtener_punto_y_direccion(selection_detail):
        if selection_detail.HasSubObjects:
            for sub_obj in selection_detail.SubObjects:
                if isinstance(sub_obj, Part.Edge):
                    punto_medio = sub_obj.CenterOfMass
                    tangente = sub_obj.tangentAt(0.5).normalize()
                    direccion_perpendicular = FreeCAD.Vector(-tangente.y, tangente.x, 0).normalize()
                    return punto_medio, direccion_perpendicular
                elif isinstance(sub_obj, Part.Face):
                    punto_centro = sub_obj.CenterOfMass
                    normal = sub_obj.normalAt(0.5, 0.5).normalize()
                    return punto_centro, normal
        return None, None

    punto1, direccion1 = obtener_punto_y_direccion(selected_objects[0])
    punto2, direccion2 = obtener_punto_y_direccion(selected_objects[1])

    if punto1 is None or punto2 is None:
        FreeCAD.Console.PrintError("Error al obtener los puntos de conexión.\n")
        return

    distancia_x = abs(punto1.x - punto2.x)
    distancia_y = abs(punto1.y - punto2.y)
    distancia_z = abs(punto1.z - punto2.z)
    distancia_central = max(distancia_x, distancia_y, distancia_z) / 2

    punto_intermedio1 = punto1 + (direccion1 * 20)
    punto_intermedio2 = punto2 + (direccion2 * 20)

    if distancia_x > distancia_y:
        punto_intermedio1.x = (punto1.x + punto2.x) / 2
        punto_intermedio2.x = punto_intermedio1.x
    else:
        punto_intermedio1.y = (punto1.y + punto2.y) / 2
        punto_intermedio2.y = punto_intermedio1.y

    radio_fillet = max(5 * (math.floor((distancia_central / 8) / 5)), 5)

    FreeCAD.Console.PrintMessage("\nPuntos generados para la conexión:\n")
    FreeCAD.Console.PrintMessage(f"  - Punto 1 (Inicio): {punto1}\n")
    FreeCAD.Console.PrintMessage(f"  - Salida Perpendicular 1: {punto_intermedio1}\n")
    FreeCAD.Console.PrintMessage(f"  - Salida Perpendicular 2: {punto_intermedio2}\n")
    FreeCAD.Console.PrintMessage(f"  - Punto 4 (Final): {punto2}\n")
    FreeCAD.Console.PrintMessage(f"  - Radio de Fillet: {radio_fillet}\n")

    puntos = [punto1, punto_intermedio1, punto_intermedio2, punto2]
    wire = Draft.make_wire(puntos, closed=False)
    wire.Label = f'Conexion_eSe_{selected_objects[0].Object.Name}_{selected_objects[1].Object.Name}'
    wire.FilletRadius = radio_fillet

    doc.recompute()

conectar_objetos_en_eSe()
