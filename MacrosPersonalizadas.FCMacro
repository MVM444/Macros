# -*- coding: utf-8 -*-
"""
Macro: MenuMacrosPersonalizadas
Descripcion: Crea menus de macros personalizadas y recientes.
- Construye un menu con todas las macros encontradas en MacroPath.
- Construye un menu con las macros mas recientes (hasta 5 entradas).
- Actualiza rutas si las macros se movieron a Macros-de-Freecad o Resources.
- Evita duplicados y omite carpetas temporales.

Autor: ChatGPT
Fecha: 2025-09-18
"""

# Qt compatibility for FreeCAD 1.x (PySide6) and older builds.
def _ensure_qt_compat():
    import sys
    import types

    QtCore = QtGui = QtWidgets = None
    binding_name = None

    for candidate in ("PySide6", "PySide2", "PySide"):
        try:
            if candidate == "PySide":
                from PySide import QtCore as _QtCore, QtGui as _QtGui
                _QtWidgets = _QtGui
            else:
                module = __import__(candidate, fromlist=["QtCore", "QtGui", "QtWidgets"])
                _QtCore = module.QtCore
                _QtGui = module.QtGui
                _QtWidgets = module.QtWidgets
            QtCore, QtGui, QtWidgets = _QtCore, _QtGui, _QtWidgets
            binding_name = candidate
            break
        except Exception:
            continue

    if QtCore is None:
        return

    qtgui_compat = types.ModuleType("QtGui")
    qtgui_compat.__dict__.update(getattr(QtGui, "__dict__", {}))
    qtgui_compat.__dict__.update(getattr(QtWidgets, "__dict__", {}))

    qtsvg_compat = None
    for module_name in ("QtSvg", "QtSvgWidgets"):
        try:
            module = __import__(binding_name, fromlist=[module_name])
            qt_module = getattr(module, module_name)
        except Exception:
            continue
        if qtsvg_compat is None:
            qtsvg_compat = types.ModuleType("QtSvg")
        qtsvg_compat.__dict__.update(getattr(qt_module, "__dict__", {}))

    qtuitools_compat = None
    try:
        module = __import__(binding_name, fromlist=["QtUiTools"])
        qtuitools_compat = module.QtUiTools
    except Exception:
        pass

    for package_name in ("PySide2", "PySide"):
        package = sys.modules.get(package_name)
        if package is None:
            package = types.ModuleType(package_name)
            sys.modules[package_name] = package
        package.QtCore = QtCore
        package.QtGui = qtgui_compat
        package.QtWidgets = QtWidgets
        sys.modules[package_name + ".QtCore"] = QtCore
        sys.modules[package_name + ".QtGui"] = qtgui_compat
        sys.modules[package_name + ".QtWidgets"] = QtWidgets
        if qtsvg_compat is not None:
            package.QtSvg = qtsvg_compat
            sys.modules[package_name + ".QtSvg"] = qtsvg_compat
        if qtuitools_compat is not None:
            package.QtUiTools = qtuitools_compat
            sys.modules[package_name + ".QtUiTools"] = qtuitools_compat


_ensure_qt_compat()

import FreeCAD
import FreeCADGui
import os
import json
from functools import partial
try:
    from PySide2 import QtCore, QtWidgets
except Exception:
    from PySide import QtCore, QtGui as QtWidgets
try:
    from shiboken2 import isValid as _qt_is_valid
except Exception:
    try:
        from shiboken import isValid as _qt_is_valid
    except Exception:
        _qt_is_valid = None

MAX_RECENT = 5
_RESOLVE_CACHE = {}
_SEARCH_PREFIXES = ("", "Macros-de-Freecad", os.path.join("Macros-de-Freecad", "Resources"))
_MENU_TITLES = ("Macros Frecuentes", "Macros Personalizadas")
_CONTROLLER_ATTR = "_macros_personalizadas_controller"
_RECENT_MENU_OBJECT = "MacrosPersonalizadas.RecentMenu"
_CUSTOM_MENU_OBJECT = "MacrosPersonalizadas.CustomMenu"


def _is_alive_qobject(obj):
    if obj is None:
        return False
    if _qt_is_valid is not None:
        try:
            return bool(_qt_is_valid(obj))
        except Exception:
            return False
    try:
        obj.objectName()
        return True
    except RuntimeError:
        return False
    except Exception:
        return True


def _macro_path_entries():
    param = FreeCAD.ParamGet("User parameter:BaseApp/Preferences/Macro").GetString("MacroPath", "")
    entries = []
    if param:
        sep = ";" if os.name == "nt" else ":"
        for part in param.split(sep):
            part = part.strip()
            if part:
                full = os.path.normpath(os.path.abspath(part))
                if full not in entries:
                    entries.append(full)
    try:
        user_dir = FreeCAD.getUserMacroDir()
    except Exception:
        user_dir = ""
    if user_dir:
        full = os.path.normpath(os.path.abspath(user_dir))
        if full not in entries:
            entries.append(full)
    return entries


def _search_roots():
    roots = []
    seen = set()
    for base in _macro_path_entries():
        for extra in _SEARCH_PREFIXES:
            candidate = os.path.join(base, extra) if extra else base
            candidate = os.path.normpath(candidate)
            if candidate not in seen:
                roots.append(candidate)
                seen.add(candidate)
    return roots


def _candidate_relpaths(rel):
    rel = rel.replace("\\", "/")
    parts = [p for p in rel.split("/") if p and p != "."]
    variants = []

    def add(parts_list):
        if not parts_list:
            return
        candidate = os.path.join(*parts_list)
        if candidate not in variants:
            variants.append(candidate)

    if parts:
        add(parts)
        if parts[0].lower() == "macros-de-freecad":
            add(parts[1:])
            add(["Macros-de-Freecad", "Resources"] + parts[1:])
        else:
            add(["Macros-de-Freecad"] + parts)
            add(["Macros-de-Freecad", "Resources"] + parts)
        if parts[0].lower() == "resources":
            add(parts[1:])
        else:
            add(["Resources"] + parts)
    return [v for v in variants if v]


def _resolve_macro_path(path):
    if not path:
        return path
    norm = os.path.normpath(path)
    key = os.path.normcase(norm)
    cached = _RESOLVE_CACHE.get(key)
    if cached:
        return cached
    if os.path.exists(norm):
        _RESOLVE_CACHE[key] = norm
        return norm
    for base in _macro_path_entries():
        try:
            rel = os.path.relpath(norm, base)
        except Exception:
            continue
        if rel.startswith(".."):
            continue
        for candidate_rel in _candidate_relpaths(rel):
            candidate = os.path.normpath(os.path.join(base, candidate_rel))
            if os.path.exists(candidate):
                _RESOLVE_CACHE[key] = candidate
                return candidate
    filename = os.path.basename(norm)
    for root in _search_roots():
        if not os.path.isdir(root):
            continue
        for dirpath, _, files in os.walk(root):
            if filename in files:
                resolved = os.path.normpath(os.path.join(dirpath, filename))
                _RESOLVE_CACHE[key] = resolved
                return resolved
    _RESOLVE_CACHE[key] = norm
    return norm


def _primary_macro_dir():
    entries = _macro_path_entries()
    return entries[0] if entries else ""


def _recent_file_path():
    base = _primary_macro_dir()
    if not base:
        return ""
    return os.path.normpath(os.path.join(base, ".macro_recent.json"))


def _usage_file_path():
    base = _primary_macro_dir()
    if not base:
        return ""
    return os.path.normpath(os.path.join(base, ".macro_usage.json"))


def _script_dir():
    try:
        return os.path.dirname(os.path.abspath(__file__))
    except Exception:
        return ""


def _unique_existing_paths(paths):
    out = []
    seen = set()
    for path in list(paths or []):
        if not path:
            continue
        p = os.path.normpath(path)
        key = os.path.normcase(p)
        if key in seen:
            continue
        seen.add(key)
        out.append(p)
    return out


def _recent_file_candidates():
    candidates = []
    primary = _recent_file_path()
    if primary:
        candidates.append(primary)
    for base in _macro_path_entries():
        candidates.append(os.path.join(base, ".macro_recent.json"))
    sdir = _script_dir()
    if sdir:
        candidates.append(os.path.join(sdir, ".macro_recent.json"))
    candidates.append(os.path.join(os.getcwd(), ".macro_recent.json"))
    return _unique_existing_paths(candidates)


def _usage_file_candidates():
    candidates = []
    primary = _usage_file_path()
    if primary:
        candidates.append(primary)
    for base in _macro_path_entries():
        candidates.append(os.path.join(base, ".macro_usage.json"))
    sdir = _script_dir()
    if sdir:
        candidates.append(os.path.join(sdir, ".macro_usage.json"))
    candidates.append(os.path.join(os.getcwd(), ".macro_usage.json"))
    return _unique_existing_paths(candidates)


def _load_json_list(path):
    if not path or not os.path.exists(path):
        return []
    try:
        with open(path, "r", encoding="utf-8") as handle:
            data = json.load(handle)
    except Exception:
        return []
    return data if isinstance(data, list) else []


def _load_json_dict(path):
    if not path or not os.path.exists(path):
        return {}
    try:
        with open(path, "r", encoding="utf-8") as handle:
            data = json.load(handle)
    except Exception:
        return {}
    return data if isinstance(data, dict) else {}


def load_recent():
    raw_recent = []
    raw_seen = set()
    for candidate in _recent_file_candidates():
        for item in _load_json_list(candidate):
            key = os.path.normcase(os.path.normpath(str(item)))
            if key in raw_seen:
                continue
            raw_seen.add(key)
            raw_recent.append(str(item))

    resolved = []
    changed = False
    for item in raw_recent:
        resolved_item = _resolve_macro_path(item)
        if resolved_item != item:
            changed = True
        if os.path.exists(resolved_item) and resolved_item not in resolved:
            resolved.append(resolved_item)

    if len(resolved) < MAX_RECENT:
        usage_candidates = []
        for candidate in _usage_file_candidates():
            usage_data = _load_json_dict(candidate)
            pairs = []
            for p, count in usage_data.items():
                try:
                    score = int(count)
                except Exception:
                    score = 0
                pairs.append((score, str(p)))
            pairs.sort(key=lambda x: x[0], reverse=True)
            usage_candidates.extend([p for _score, p in pairs])
        for item in usage_candidates:
            if len(resolved) >= MAX_RECENT:
                break
            normalized = os.path.normpath(str(item).replace("/", os.sep))
            resolved_item = _resolve_macro_path(normalized)
            if os.path.exists(resolved_item) and resolved_item not in resolved:
                resolved.append(resolved_item)

    resolved = resolved[:MAX_RECENT]
    if changed or len(resolved) != len(raw_recent):
        save_recent(resolved)
    return resolved


def save_recent(lst):
    path = _recent_file_path()
    if not path:
        candidates = _recent_file_candidates()
        path = candidates[0] if candidates else ""
    if not path:
        return
    try:
        folder = os.path.dirname(path)
        if folder and not os.path.isdir(folder):
            os.makedirs(folder, exist_ok=True)
        with open(path, "w", encoding="utf-8") as handle:
            json.dump(lst[:MAX_RECENT], handle, indent=2)
    except Exception as err:
        FreeCAD.Console.PrintError(f"Error guardando recien usadas: {err}\n")


def populate_recent_menu(menu):
    if not _is_alive_qobject(menu):
        return
    try:
        menu.clear()
    except RuntimeError:
        return
    paths = load_recent()
    if not paths:
        try:
            empty = menu.addAction("(Sin macros recientes)")
            empty.setEnabled(False)
        except Exception:
            pass
        return
    for path in paths:
        if not _is_alive_qobject(menu):
            return
        name = os.path.splitext(os.path.basename(path))[0]
        try:
            action = menu.addAction(name)
        except RuntimeError:
            return
        action.setToolTip(path)
        action.triggered.connect(partial(run_macro, path))


def _refresh_recent_menu_safe():
    bar = _menu_bar()
    if bar is None:
        return
    for menu in _top_level_menus(bar):
        if not _is_alive_qobject(menu):
            continue
        try:
            if menu.objectName() == _RECENT_MENU_OBJECT:
                populate_recent_menu(menu)
                return
        except RuntimeError:
            continue
        except Exception:
            continue


def create_recent_menu(bar):
    freq = bar.addMenu("Macros Frecuentes")
    freq.setObjectName(_RECENT_MENU_OBJECT)
    freq.aboutToShow.connect(partial(populate_recent_menu, freq))
    populate_recent_menu(freq)
    return freq


def _ensure_menu(cache, parts):
    if not parts:
        return cache[()]
    key = tuple(parts)
    if key in cache:
        return cache[key]
    parent = _ensure_menu(cache, parts[:-1])
    menu = parent.addMenu(parts[-1])
    cache[key] = menu
    return menu


def create_custom_menu(bar):
    custom = bar.addMenu("Macros Personalizadas")
    custom.setObjectName(_CUSTOM_MENU_OBJECT)
    bases = _macro_path_entries()
    if not bases:
        FreeCAD.Console.PrintError("Directorio de macros no existe.\n")
        return None
    menu_cache = {(): custom}
    seen = set()
    primary_base = next((b for b in bases if os.path.isdir(b)), bases[0])
    primary_norm = os.path.normcase(os.path.abspath(primary_base))

    for base in bases:
        if not os.path.isdir(base):
            continue
        base_label = os.path.basename(base.rstrip("\/"))
        base_tag = base_label or base
        is_primary = os.path.normcase(os.path.abspath(base)) == primary_norm
        for root, dirs, files in os.walk(base):
            dirs[:] = [d for d in dirs if d not in {".git", "__pycache__", ".vscode"}]
            macro_files = [f for f in files if f.lower().endswith(".fcmacro")]
            if not macro_files:
                continue
            rel = os.path.relpath(root, base)
            rel_parts = [p for p in rel.replace("\\", "/").split("/") if p and p != "."]
            if is_primary:
                target_parts = rel_parts
            else:
                if rel_parts:
                    target_parts = [base_tag] + rel_parts
                else:
                    target_parts = [base_tag]
            submenu = _ensure_menu(menu_cache, target_parts)
            for fname in sorted(macro_files):
                full = os.path.normpath(os.path.join(root, fname))
                key = os.path.normcase(full)
                if key in seen:
                    continue
                seen.add(key)
                label = os.path.splitext(fname)[0]
                action = submenu.addAction(label)
                action.setToolTip(full)
                action.triggered.connect(partial(run_macro, full))
    return custom


def _main_window():
    try:
        return FreeCADGui.getMainWindow()
    except Exception:
        return None


def _menu_bar():
    mw = _main_window()
    if mw is None:
        return None
    try:
        return mw.menuBar()
    except Exception:
        return None


def _top_level_menus(bar):
    menus = []
    try:
        actions = list(bar.actions())
    except Exception:
        return menus
    for action in actions:
        try:
            menu = action.menu()
        except Exception:
            menu = None
        if menu is not None:
            menus.append(menu)
    return menus


def _top_level_menu_count(bar, title):
    count = 0
    for menu in _top_level_menus(bar):
        try:
            if menu.title() == title:
                count += 1
        except Exception:
            continue
    return count


def _is_managed_menu(menu):
    try:
        if menu.objectName() in {_RECENT_MENU_OBJECT, _CUSTOM_MENU_OBJECT}:
            return True
    except Exception:
        pass
    try:
        return menu.title() in _MENU_TITLES
    except Exception:
        return False


def _remove_managed_menus():
    mw = _main_window()
    bar = _menu_bar()
    if mw is None or bar is None:
        return

    for action in list(bar.actions()):
        try:
            menu = action.menu()
        except Exception:
            menu = None
        if menu is not None and _is_managed_menu(menu):
            bar.removeAction(action)

    for menu in list(mw.findChildren(QtWidgets.QMenu)):
        if not _is_managed_menu(menu):
            continue
        try:
            parent = menu.parentWidget()
            if isinstance(parent, QtWidgets.QMenuBar):
                parent.removeAction(menu.menuAction())
            elif isinstance(parent, QtWidgets.QMenu):
                parent.removeAction(menu.menuAction())
        except Exception:
            pass
        try:
            menu.deleteLater()
        except Exception:
            pass

def recreate_menus():
    bar = _menu_bar()
    if bar is None:
        return
    _remove_managed_menus()
    create_recent_menu(bar)
    create_custom_menu(bar)


def run_macro(path):
    target = _resolve_macro_path(path)
    if not target or not os.path.exists(target):
        FreeCAD.Console.PrintError(f"No se encontro la macro: {target}\n")
        return
    recent = load_recent()
    if target in recent:
        recent.remove(target)
    recent.insert(0, target)
    save_recent(recent)
    try:
        with open(target, "r", encoding="utf-8", errors="ignore") as handle:
            source = handle.read()
        exec(compile(source, target, "exec"), {"__file__": target, "__name__": "__main__"})
    except Exception as err:
        FreeCAD.Console.PrintError(f"Error en macro {target}: {err}\n")
    bar = _menu_bar()
    if bar is None:
        return
    _refresh_recent_menu_safe()


class _MenuPersistenceController(QtCore.QObject):
    def __init__(self):
        super().__init__()
        self._main_window = None
        self._connected = False
        self._startup = QtCore.QTimer(self)
        self._startup.setInterval(500)
        self._startup.timeout.connect(self._on_startup_tick)
        self._refresh = QtCore.QTimer(self)
        self._refresh.setSingleShot(True)
        self._refresh.timeout.connect(self._refresh_menus)

    def start(self):
        if not self._startup.isActive():
            self._startup.start()
        self.schedule_refresh(0)

    def _on_startup_tick(self):
        mw = _main_window()
        if mw is None:
            return
        try:
            if not mw.property("eventLoop"):
                return
        except Exception:
            pass
        self._bind_main_window(mw)
        self._startup.stop()
        self.schedule_refresh(0)

    def _bind_main_window(self, mw):
        if mw is None or (self._connected and mw is self._main_window):
            return
        self._main_window = mw
        try:
            mw.workbenchActivated.connect(self._on_workbench_activated)
        except Exception:
            pass
        try:
            mw.mainWindowClosed.connect(self._on_main_window_closed)
        except Exception:
            pass
        self._connected = True

    def _on_workbench_activated(self, *args):
        del args
        self.schedule_refresh(250)

    def schedule_refresh(self, delay=0):
        try:
            self._refresh.start(max(0, int(delay)))
        except Exception:
            recreate_menus()

    def _refresh_menus(self):
        recreate_menus()

    def _on_main_window_closed(self):
        self._startup.stop()
        self._refresh.stop()

    def shutdown(self):
        try:
            self._startup.stop()
        except Exception:
            pass
        try:
            self._refresh.stop()
        except Exception:
            pass


def install():
    if not FreeCAD.GuiUp:
        return None
    controller = getattr(FreeCADGui, _CONTROLLER_ATTR, None)
    if controller is not None and not isinstance(controller, _MenuPersistenceController):
        try:
            if hasattr(controller, "shutdown") and callable(getattr(controller, "shutdown")):
                controller.shutdown()
            else:
                for timer_name in ("_startup", "_refresh"):
                    tmr = getattr(controller, timer_name, None)
                    if tmr is not None and hasattr(tmr, "stop"):
                        tmr.stop()
        except Exception:
            pass
        controller = None
    if controller is None:
        controller = _MenuPersistenceController()
        setattr(FreeCADGui, _CONTROLLER_ATTR, controller)
    controller.start()
    try:
        recreate_menus()
    except Exception:
        controller.schedule_refresh(0)
    controller.schedule_refresh(250)
    return controller


if FreeCAD.GuiUp:
    install()
