# -*- coding: utf-8 -*-
# MenuText: Extraer propiedades del objeto
# ToolTip: Extrae las propiedades de los objetos seleccionados y las copia como JSON.
# Version: 2.0.0 | Date: 2026-08-12 00:00 CST
"""Serialize selected objects safely with depth and size limits; read-only."""

import json

import FreeCAD as App
import FreeCADGui as Gui

from programacion_common import clipboard_set, document_metadata, info, link_data, path_text, text, warning

TOOL = "PROPIEDADES"
MAX_DEPTH = 4
MAX_ITEMS = 100
MAX_TEXT = 4000


def safe(value, depth=0):
    if depth >= MAX_DEPTH:
        return "<limite de profundidad>"
    if value is None or isinstance(value, (bool, int, float)):
        return value
    if isinstance(value, str):
        return value[:MAX_TEXT] + ("<truncado>" if len(value) > MAX_TEXT else "")
    if hasattr(value, "Value") and hasattr(value, "Unit"):
        return {"value": float(value.Value), "unit": text(value.Unit)}
    if all(hasattr(value, key) for key in ("x", "y", "z")):
        return {"x": float(value.x), "y": float(value.y), "z": float(value.z)}
    if hasattr(value, "Name") and hasattr(value, "TypeId"):
        return {"Name": text(value.Name), "Label": text(getattr(value, "Label", "")), "TypeId": text(value.TypeId)}
    if isinstance(value, dict):
        return {text(key): safe(item, depth + 1) for key, item in list(value.items())[:MAX_ITEMS]}
    if isinstance(value, (list, tuple)):
        result = [safe(item, depth + 1) for item in list(value)[:MAX_ITEMS]]
        if len(value) > MAX_ITEMS:
            result.append("<{} elementos omitidos>".format(len(value) - MAX_ITEMS))
        return result
    rendered = text(value, "<no serializable>")
    return rendered[:MAX_TEXT] + ("<truncado>" if len(rendered) > MAX_TEXT else "")


def record(obj):
    failures = []
    props = {}
    for name in list(getattr(obj, "PropertiesList", []) or []):
        try:
            props[name] = safe(obj.getPropertyByName(name))
        except Exception as exc:
            failures.append({"property": name, "error": text(exc)})
    return {
        "Name": text(getattr(obj, "Name", "")),
        "Label": text(getattr(obj, "Label", "")),
        "TypeId": text(getattr(obj, "TypeId", "")),
        "paths": path_text(obj),
        "link": link_data(obj),
        "properties": props,
        "serialization_failures": failures,
    }


def main():
    objects = list(Gui.Selection.getSelection() or [])
    if not objects:
        warning(TOOL, "No hay objetos seleccionados.")
        return
    payload = {"document": document_metadata(), "objects": [record(obj) for obj in objects]}
    value = json.dumps(payload, ensure_ascii=False, indent=2, sort_keys=True)
    clipboard_set(value)
    failures = sum(len(item["serialization_failures"]) for item in payload["objects"])
    info(TOOL, "JSON copiado. Objetos={}; propiedades no leidas={}.".format(len(objects), failures))


main()
