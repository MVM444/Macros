# -*- coding: utf-8 -*-
# MenuText: Copiar ultimo minuto
# ToolTip: Copia el ultimo minuto de la Vista de reportes, con respaldo FreeCAD.log.
# Version: 2.0.0 | Date: 2026-08-12 00:00 CST
"""Copy the latest report/log minute with diagnostic context; does not edit documents."""

import datetime
import os
import re

import FreeCAD as App
import FreeCADGui as Gui

from programacion_common import clipboard_set, document_metadata, freecad_version, info, warning

TOOL = "ULTIMO_MINUTO"
STAMP = re.compile(r"(?<!\d)([01]\d|2[0-3]):([0-5]\d):([0-5]\d)(?!\d)")


def seconds(line):
    match = STAMP.search(line[:80])
    if not match:
        return None
    return int(match.group(1)) * 3600 + int(match.group(2)) * 60 + int(match.group(3))


def last_minute(lines):
    lines = list(lines or [])
    end = len(lines) - 1
    while end >= 0 and not lines[end].strip():
        end -= 1
    if end < 0:
        return []
    anchor_index = end
    while anchor_index >= 0 and seconds(lines[anchor_index]) is None:
        anchor_index -= 1
    if anchor_index < 0:
        return lines[max(0, end - 200):end + 1]
    anchor = seconds(lines[anchor_index])
    selected = []
    for index in range(end, -1, -1):
        stamp = seconds(lines[index])
        if stamp is not None:
            age = (anchor - stamp) % 86400
            if age > 60 and age < 86340:
                break
        selected.append(lines[index])
    selected.reverse()
    return selected


def report_text():
    _core, _gui, widgets = __import__("programacion_common").qt_modules()
    main = Gui.getMainWindow()
    candidates = []
    for widget_type in (widgets.QPlainTextEdit, widgets.QTextEdit):
        for widget in list(main.findChildren(widget_type) or []):
            name = (str(widget.objectName()) + " " + str(widget.windowTitle())).lower()
            parent = widget.parent()
            while parent is not None and len(name) < 1000:
                try:
                    name += " " + str(parent.objectName()) + " " + str(parent.windowTitle())
                    parent = parent.parent()
                except Exception:
                    break
            score = sum(token in name for token in ("report", "reporte", "reportview"))
            if score:
                candidates.append((score, widget))
    candidates.sort(key=lambda item: item[0], reverse=True)
    for _score, widget in candidates:
        try:
            value = widget.toPlainText()
            if value:
                return value, "Vista de reportes"
        except Exception:
            continue
    return "", ""


def log_path():
    for getter in ("getLogFileName", "getLogFilename"):
        try:
            value = getattr(App, getter)()
            if value and os.path.isfile(value):
                return value
        except Exception:
            pass
    appdata = os.environ.get("APPDATA", "")
    value = os.path.join(appdata, "FreeCAD", "FreeCAD.log") if appdata else ""
    return value if os.path.isfile(value) else ""


def main():
    raw, source = report_text()
    if not raw:
        path = log_path()
        if path:
            with open(path, "r", encoding="utf-8", errors="replace") as handle:
                raw = handle.read()
            source = "FreeCAD.log ({})".format(path)
    if not raw:
        warning(TOOL, "No se pudo leer la Vista de reportes ni FreeCAD.log.")
        return
    block = last_minute(raw.splitlines())
    meta = document_metadata()
    now = datetime.datetime.now().astimezone().isoformat(timespec="seconds")
    header = [
        "Contexto para GPT/Codex",
        "Documento: {} ({})".format(meta["label"] or "sin documento", meta["name"] or "-") ,
        "Archivo activo: {}".format(meta["file"] or "no guardado"),
        "FreeCAD: {}".format(freecad_version()),
        "Fecha y hora: {}".format(now),
        "Fuente: {}".format(source),
        "----- INICIO REGISTRO -----",
    ]
    clipboard_set("\n".join(header + block + ["----- FIN REGISTRO -----"]))
    info(TOOL, "Copiado desde {}. Lineas={}.".format(source, len(block)))


main()
