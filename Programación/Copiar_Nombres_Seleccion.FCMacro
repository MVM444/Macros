# -*- coding: utf-8 -*-
# MenuText: Copiar resumen de seleccion
# ToolTip: Copia identidad, rutas, tipos y Links de la seleccion sin modificar objetos.
# Version: 2.0.0 | Date: 2026-08-12 00:00 CST
"""Create a compact, read-only summary of selected FreeCAD objects."""

from collections import Counter

import FreeCADGui as Gui

from programacion_common import clipboard_set, info, link_data, path_text, text, warning

TOOL = "SELECCION"


def main():
    objects = list(Gui.Selection.getSelection() or [])
    if not objects:
        warning(TOOL, "No hay objetos seleccionados.")
        return
    counts = Counter(text(getattr(obj, "TypeId", "")) or "<sin TypeId>" for obj in objects)
    lines = ["Resumen de seleccion", "Cantidad: {}".format(len(objects)), "", "Conteo por tipo:"]
    lines.extend("- {}: {}".format(key, counts[key]) for key in sorted(counts))
    lines.append("\nObjetos:")
    for index, obj in enumerate(objects, 1):
        links = link_data(obj)
        lines.append("{}. Name={} | Label={} | TypeId={}".format(
            index, text(getattr(obj, "Name", "")), text(getattr(obj, "Label", "")),
            text(getattr(obj, "TypeId", ""))))
        for path in path_text(obj):
            lines.append("   Ruta: " + path)
        if links["is_link"]:
            lines.append("   Link: {} [{}]".format(links["linked_label"] or "?", links["linked_name"] or "?"))
    clipboard_set("\n".join(lines))
    info(TOOL, "Resumen copiado. Objetos={}; tipos={}.".format(len(objects), len(counts)))


main()
